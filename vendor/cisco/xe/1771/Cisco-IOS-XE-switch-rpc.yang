module Cisco-IOS-XE-switch-rpc {
  namespace "http://cisco.com/ns/yang/Cisco-IOS-XE-switch-rpc";
  prefix ios-xe-sw-rpc;

  import cisco-semver {
    prefix cisco-semver;
  }
  import Cisco-IOS-XE-rpc {
    prefix ios-xe-rpc;
  }

  organization
    "Cisco Systems";
  contact
    "<mailto:cs-yang@cisco.com>";
  description
    "NED Switch RPC YANG module for IOS
     Copyright (c) 2016-2019 by Cisco Systems, Inc.
     All rights reserved.";

  revision 2020-03-01 {
    description
      "Added factory-reset";
    cisco-semver:module-version "1.2.0";
  }
  revision 2019-11-01 {
    description
      "Added new augment statement";
    cisco-semver:module-version "1.1.0";
  }
  revision 2019-07-01 {
    description
      "Establish semantic version baseline";
    cisco-semver:module-version "1.0.0";
  }
  revision 2019-02-11 {
    description
      "increased stacking switch range from 9 to 16";
  }
  revision 2018-12-06 {
    description
      "created for NED RPC modularisation";
  }

  rpc switch {
    input {
      leaf switch-number-drop-node-name {
        mandatory true;
        type uint8 {
          range "1..16";
        }
      }
      choice pri-renum-stack {
        mandatory true;
        case priority-case {
          leaf priority {
            description
              "<1-15>  Switch Priority";
            type uint8 {
              range "1..15";
            }
          }
        }
        case renumver-case {
          leaf renumber {
            description
              "<1-16>  New number of the Switch";
            type uint8 {
              range "1..16";
            }
          }
        }
        case stack-case {
          container stack {
            leaf port {
              description
                "<1-2>  Stack port number to enable/disable";
              type uint8 {
                range "1..2";
              }
            }
          }
        }
      }
    }
    output {
      uses ios-xe-rpc:cisco-xe-rpc-output;
    }
  }

  augment "/ios-xe-rpc:reload/ios-xe-rpc:input" {
    leaf slot {
      description
        "Slot number of RP or line card";
      type uint8 {
        range "1..16";
      }
    }
  }

  augment "/ios-xe-rpc:factory-reset/ios-xe-rpc:input" {
    container switch {
      description
        "Switch in the system";
      choice switch-number-options {
        case switch-number-case {
          leaf switch-number-drop-node-name {
            description
              "Switch number in the Stack";
            type uint8 {
              range "1..16";
            }
          }
        }
        case switch-all-case {
          container all-drop-node-name {
            leaf all {
              description
                "All Switches in the Stack";
              type empty;
            }
          }
        }
      }
      choice clear-choice {
        case clear-all {
          container clear-all-drop-node-name {
            leaf all {
              description
                "All factory reset operations";
              type empty;
            }
          }
        }
        case clear-all-3-pass {
          container all {
            container secure {
              description
                "Secure";
              leaf alt-name-3-pass {
                description
                  "3-pass";
                type empty;
              }
            }
          }
        }
        case clear-boot-vars {
          leaf boot-vars {
            description
              "boot-vars";
            type empty;
          }
        }
        case clear-config {
          leaf config {
            description
              "config";
            type empty;
          }
        }
      }
    }
  }
}
